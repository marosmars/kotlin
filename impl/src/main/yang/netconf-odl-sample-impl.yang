module netconf-odl-sample-impl {
    yang-version 1;
    namespace "urn:opendaylight:params:xml:ns:yang:netconf-odl-sample:impl";
    prefix "netconf-odl-sample-impl";

    import config { prefix config; revision-date 2013-04-05; }
    import opendaylight-md-sal-binding { prefix md-sal-binding; revision-date 2013-10-28;}

    description
        "Service definition for netconf-odl-sample project";

    revision "2014-12-10" {
        description
            "Initial revision";
    }

    identity netconf-odl-sample {
        base config:module-type;
        config:java-name-prefix NetconfSample;
    }

    augment "/config:modules/config:module/config:configuration" {
        case netconf-odl-sample {
            when "/config:modules/config:module/config:type = 'netconf-odl-sample'";
            container broker {
                uses config:service-ref {
                    refine type {
                        mandatory true;
                        config:required-identity md-sal-binding:binding-broker-osgi-registry;
                    }
                }
            }
        }
    }
}
